# Specification: Specification Document
- Description: Requirements Document

## REQ-1 (Heading)
<ANALYSISFUNCTION>

### REQ-3 (Requirement Type)
The analysis function <ANALYSISFUNCTION> is a subfunction of the analysis function <PARENTFUNCTION>.

### REQ-4 (Requirement Type)
The analysis function <ANALYSISFUNCTION> has the following purpose: "PURPOSE".

### REQ-5 (Heading)
Inputs & Outputs

#### REQ-7 (Requirement Type)
The following information is used by the analysis function <ANALYSISFUNCTION>: <INPUTS>.

#### REQ-8 (Requirement Type)
The following information is created by the analysis function <ANALYSISFUNCTION>: <OUTPUTS>.

### REQ-6 (Heading)
Subfunctions

## REQ-2 (Free Text)
Sample Free-Text Requirement
