# Specification: Specification Document
- Description: Requirements Document

## REQ-1 (Heading)
Body Control Module

### REQ-8 (Requirement Type)
The top-level function is called BodyControlModule.

### REQ-2 (Heading)
External Systems

### REQ-3 (Heading)
Inputs & Outputs

#### REQ-9 (Requirement Type)
The following information is received by the function BodyControlModule: indicationRequest, unlockRequest.

### REQ-4 (Heading)
Subfunctions

#### REQ-5 (Heading)
Lighting

##### REQ-10 (Requirement Type)
The function Lighting is a subfunction of the function BodyControlModule.

##### REQ-15 (Requirement Type)
The function Lighting has the following purpose: "Control the turn signals and brake light".

##### REQ-6 (Heading)
Inputs & Outputs

###### REQ-11 (Requirement Type)
The following information is used by the function Lighting: indicationRequest.

#### REQ-12 (Heading)
Central Locking

##### REQ-13 (Requirement Type)
The function CentralLocking is a subfunction of the function BodyControlModule.

##### REQ-14 (Heading)
Inputs & Outputs

## REQ-7 (Free Text)
