# Specification: Specification Document
- Description: Requirements Document

## REQ-1 (Heading)
<TOPLEVELANALYSISFUNCTION>

### REQ-3 (Requirement Type)
The top-level analysis function is called <TOPLEVELANALYSISFUNCTION>.

### REQ-4 (Heading)
External Systems

### REQ-5 (Heading)
Inputs & Outputs

#### REQ-7 (Requirement Type)
The following information is received by the analysis function <TOPLEVELANALYSISFUNCTION>: <TOPLEVELINPUTS>.

#### REQ-8 (Requirement Type)
The following information is sent from the analysis function <TOPLEVELANALYSISFUNCTION>: <TOPLEVELOUTPUTS>.

### REQ-6 (Heading)
Subfunctions
